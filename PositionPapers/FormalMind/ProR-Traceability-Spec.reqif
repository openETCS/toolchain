# Specification: Specification Document
- Description: Requirements

## R2 (Headline Type)
ProR-based Traceability

## R1 (Requirement Type Plain)
Specification for openETCS

## R3 (Headline Type)
Problem Description
- Label: 1

### R4 (Requirement Type Plain)
One high-priority need for WP3 and WP4 in openETCS is the traceability between ProR requirements and Papyrus SysML models.  Several options have been evaluated, in particular at the Paris traceability workshop on February 7th.

### R5 (Requirement Type Plain)
As the most promising approach, ProR-based traceability has been identified.  In particular, this kind of traceability has already been realized for Event-B models (link).  This implementation convinced the stakeholders that such a solution would provide all the required features, in particular support for change management.

### R6 (Requirement Type Plain)
Alternative solutions have been discussed (Reqtify, ReqCycle), but none has all the required features, and none could be provided as quickly as a ProR-based solution.

## R7 (Headline Type)
Architecture
- Label: 2

### R8 (Requirement Type XHTML)
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
### R9 (Requirement Type Plain)
For this solution, SysML Proxy elements are created that hold (1) a reference to the traced Element and (2) a textual representation of that element (cache).  The actual trace is realized as a Link to the Requirement.  Now the traceability exists in ProR.
- Status: Implemented in Full

### R10 (Requirement Type Plain)
Upon rendering The SysML Proxy, the textual representation of the element will be retrieved in real time from Element , showing only current content to the user and updating the cache at the same time, if necessary.
- Status: Implemented in Full

### R11 (Requirement Type Plain)
Optional: So far, the solution would not allow traceability from SysML to the requirements (no need to even touch the Papyrus model).  To allow this, in addition to the above, the tool could, upon linking, do the following: Create a Reverse Proxy, in the form of a SysML Requirement, which would be linked (using SysML mechanisms) to Element.  The ID would hold the corresponding ReqIF ID, the Name field would hold the ReqIF human-readable ID and the Description would hold the requirements text.
- Status: Not Implemented

### R47 (Requirement Type Plain)
Furthermore, to make the links to the requirements usable in SCADE System and SCADE Suite (with Reqtify)  an entry in the way "covers: #REQ#Req_ID#REAL#" shall be added to the comment field of the SysML element, which is linked to the requirement. At doing so "covers:" it the indicator für Reqtify, "#REQ#" and "#REAL#" are delimiters and Req_ID holds the ReqIF human-readable ID of the repective requirement.
- Status: Not Implemented

## R12 (Headline Type)
Use Cases
- Label: 3

### R13 (Requirement Type Plain)
The use cases assume that the Reverse Proxy is not created.  This could be implemented at a later time.

### R14 (Headline Type)
Actors

#### R15 (Requirement Type Plain)
The following Actors exist:

#### R16 (Requirement Type Plain)
User: The person who creates and uses the traceability through the user interface.

#### R17 (Requirement Type Plain)
System: The system sometimes needs to perform actions on its own, although these are typically indirectly triggered by the user.

### R18 (Headline Type)
UC_Create_Link
- Status: Implemented in Full

#### R19 (Requirement Type Plain)
The SysML Model Explorer is open, the specification editor is open
- Label: Precondition:

#### R21 (Requirement Type Plain)
A SysML Proxy for the dragged model is retrieved (if it already exists) or created (if not).  A Link is created, if it does not exist yet.  The Requirement is the Source, the SysML Proxy is the Target.
- Label: Result:

#### R20 (Requirement Type Plain)
The user drags one or more Elements from the Model Explorer onto a Requirement.
- Label: Steps:

#### R22 (Requirement Type Plain)
If the Link already exists, another link shall not be created.
- Label: Notes:

#### R23 (Requirement Type Plain)
A flag allows source and target to be reversed.

### R24 (Headline Type)
UC_Change_Requirement
- Status: Not Implemented

#### R25 (Requirement Type Plain)
A Link from a Requirement to an Element has been created.
- Label: Precondition:

#### R26 (Requirement Type Plain)
The user edits the requirements text.
- Label: Steps:

#### R27 (Requirement Type Plain)
The Link is marked with a flag indicating that the Source (the Requirement) has changed.
- Label: Result:

### R28 (Headline Type)
UC_Change_Model_Element
- Status: Implemented in Part

#### R29 (Requirement Type Plain)
A Link from a Requirement to an Element has been created.
- Label: Precondition:

#### R30 (Requirement Type Plain)
The user edits the Element in Papyrus
- Label: Steps:

#### R31 (Requirement Type Plain)
The Link is marked with a flag indicating that the Target (the Element) has changed.
- Label: Result:

### R32 (Headline Type)
UC_Deleting_Link
- Status: Implemented in Full

#### R33 (Requirement Type Plain)
A Link from a Requirement to an Element has been created.
- Label: Precondition:

#### R34 (Requirement Type Plain)
The user removes the Link from the model
- Label: Steps:

#### R35 (Requirement Type Plain)
The Link is gone
- Label: Result:

#### R36 (Requirement Type Plain)
It has been decided to not remove the proxy
- Label: Notes:

### R37 (Headline Type)
UC_Deleting_Requirement
- Status: Implemented in Part

#### R38 (Requirement Type Plain)
A Link from a Requirement to an Element has been created.
- Label: Precondition:

#### R39 (Requirement Type Plain)
The user removes the Requirement from the model
- Label: Steps:

#### R40 (Requirement Type Plain)
The Requirement is gone.  In ProR, the Link and SysML Proxy would still exist.  The Link is marked with a flag indicating that the Source (the Requirement) has changed.
- Label: Result:

### R41 (Headline Type)
UC_Deleting_Element
- Status: Implemented in Full

#### R42 (Requirement Type Plain)
A Link from a Requirement to an Element has been created.
- Label: Precondition:

#### R43 (Requirement Type Plain)
The user removes the Element from the model (in Papyrus)
- Label: Steps:

#### R44 (Requirement Type Plain)
The Element is gone.  In ProR, the Link and SysML Proxy would still exist.  The Link would be marked as “Target (Element) changed.  The link target (the SysML Proxy) would show a warning message in red, indicating that the target cannot be found any more.  The id and cached information about the target will be intact (and could be shown as well).
- Label: Result:

### R45 (Headline Type)
UC_Verify
- Status: Not Implemented

#### R46 (Requirement Type Plain)
This Use Case still needs to be defined.
- Status: Not Implemented
